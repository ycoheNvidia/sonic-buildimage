//filename:  sonic-ssh-server.yang
module sonic-ssh-server {
    yang-version 1.1;
    namespace "http://github.com/sonic-net/sonic-ssh-server";
    prefix sshg;

    description "SSH SERVER CONFIG YANG Module for SONiC OS";

	revision 2022-08-29 {
        description
            "First Revision";
    }

    container sonic-ssh-server {
		container SSH_SERVER {
			description "SSH SERVER CONFIG part of config_db.json";
			container POLICIES {
				leaf authentication_retries {
					description "number of login attepmts";
					default 6;
					type uint32 {
						range 1..100;
					}
				}
				leaf login_timeout {
					description "login timeout (secs unit)";
					default 120;
					type uint32 {
						range 1..600;
					}
				}
				leaf ports {
					description "ssh port numbers";
					default "22";
                    type string {
                        pattern '([1-9]|[1-9]\d{1,3}|[1-5]\d{4}|6[0-4]\d{3}|65[0-4]\d{2}|655[0-2]\d|6553[0-6])(,([1-9]|[1-9]\d{1,3}|[1-5]\d{4}|6[0-4]\d{3}|65[0-4]\d{2}|655[0-2]\d|6553[0-6]))*' {
                            error-message "Invalid port numbers value";
                            error-app-tag ssh-server-ports-invalid-value;
                        }
                    }
				}
			}/*container policies */
		} /* container SSH_SERVER  */
    }/* container sonic-ssh-server */
}/* end of module sonic-ssh-server */
